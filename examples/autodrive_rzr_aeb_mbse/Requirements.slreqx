# Requirements

## 4: Safety (Functional)
The system shall prevent any collision under all valid scenarios within its operational limits. That is to say that the total number of collisions of the RZR shall be 0.

## 2: Comfort (Functional)
The planning sub-system shall ensure passenger comfort while ensuring effectiveness in stopping the vehicle. That is to say that the peak jerk experienced by the RZR shall be less than 6 m/s^3.

## 3: Tracking (Functional)
The control sub-system shall accurately track the prescribed velocity setpoint, with minimal deviation. That is to say that the average estimated velocity error shall be within acceptable bounds of ±1 m/s.

## 1: Detection (Functional)
The perception sub-system shall be able to detect various objects on the road ahead, classify them, and provide the confidence scores of the detections. That is to say that the number of detections throughout the test shall be greater than 1.
