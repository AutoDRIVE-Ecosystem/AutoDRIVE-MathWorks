# Requirements

## Path Tracking: Reach goal (Functional)
The robot shall reach its goal pose within a position tolerance of 0.5 m and orientation tolerance of 0.087 radians (5 degrees).

## Obstacle Avoidance: Stay away from obstacles (Functional)
The robot’s center of mass must stay away from obstacles by a distance equal to wheelbase or track width (whichever is greater).

## ⁠Velocity Tracking: Velocity error (Functional)
The velocity error of the robot must be less than equal to 0.27 m/s (1 km/h).

## Localization: Localization error (Functional)
The localization error must be within a position tolerance of 0.5 m and orientation tolerance of 0.087 radians (5 degrees).

## Path Planning: Planning time (Functional)
The planning time should be less than 10 seconds.
