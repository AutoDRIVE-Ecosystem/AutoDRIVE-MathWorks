# Requirements

## 4: Collision (Functional)
The system must prevent any collision under all valid scenarios within its operational limits. That is to say that the total number of collisions of the RZR should be 0.

## 2: Smoothness (Functional)
The planning subsystem should ensure passenger comfort while ensuring effectiveness in stopping the vehicle. That is to say that the peak jerk experienced by the RZR should be less than 6 m/s^2.

## 3: Velocity (Functional)
The control subsystem must accurately track the prescribed velocity setpoint, with minimal deviation. That is to say that the average estimated velocity error must be within acceptible bounds of +/- 1 m/s.

## 1: Detections (Functional)
The perception subsystem should be able to detect various objects on the road ahead, classify them, and provide the confidence scores of the detections. That is to say that the number of detections throughout the test should be greater than 1.
